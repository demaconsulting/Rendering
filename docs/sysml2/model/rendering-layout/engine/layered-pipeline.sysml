package RenderingLayout {
    private import SoftwareItemMetadata::*;

    part def LayeredPipeline {
        doc /* The ELK-style layered Sugiyama stage pipeline. */

        metadata info : SoftwareInfo {
            sourceFiles = ("src/DemaConsulting.Rendering.Layout/Engine/Layered/AxisTransform.cs", "src/DemaConsulting.Rendering.Layout/Engine/Layered/BoundaryPortResolver.cs", "src/DemaConsulting.Rendering.Layout/Engine/Layered/BrandesKopfPlacer.cs", "src/DemaConsulting.Rendering.Layout/Engine/Layered/ComponentPacker.cs", "src/DemaConsulting.Rendering.Layout/Engine/Layered/CrossingMinimizer.cs", "src/DemaConsulting.Rendering.Layout/Engine/Layered/CycleBreaker.cs", "src/DemaConsulting.Rendering.Layout/Engine/Layered/HierarchyHandling.cs", "src/DemaConsulting.Rendering.Layout/Engine/Layered/HierarchyMergeRegionBuilder.cs", "src/DemaConsulting.Rendering.Layout/Engine/Layered/ILayoutStage.cs", "src/DemaConsulting.Rendering.Layout/Engine/Layered/LayerAssigner.cs", "src/DemaConsulting.Rendering.Layout/Engine/Layered/LayeredCorridorRouter.cs", "src/DemaConsulting.Rendering.Layout/Engine/Layered/LayeredGraph.cs", "src/DemaConsulting.Rendering.Layout/Engine/Layered/LayeredLayoutMetrics.cs", "src/DemaConsulting.Rendering.Layout/Engine/Layered/LayeredLayoutPipeline.cs", "src/DemaConsulting.Rendering.Layout/Engine/Layered/LayoutDirection.cs", "src/DemaConsulting.Rendering.Layout/Engine/Layered/LongEdgeJoiner.cs", "src/DemaConsulting.Rendering.Layout/Engine/Layered/LongEdgeSplitter.cs", "src/DemaConsulting.Rendering.Layout/Engine/Layered/MergeRegionDecomposer.cs", "src/DemaConsulting.Rendering.Layout/Engine/Layered/MergeRegionGraphAssembler.cs", "src/DemaConsulting.Rendering.Layout/Engine/Layered/PortDistributor.cs", "src/DemaConsulting.Rendering.Layout/Engine/Layered/ShapeAnchorSupport.cs");
            testFiles = ("test/DemaConsulting.Rendering.Layout.Tests/Engine/Layered/AxisTransformTests.cs", "test/DemaConsulting.Rendering.Layout.Tests/Engine/Layered/BoundaryPortResolverTests.cs", "test/DemaConsulting.Rendering.Layout.Tests/Engine/Layered/BrandesKopfPlacerTests.cs", "test/DemaConsulting.Rendering.Layout.Tests/Engine/Layered/ComponentPackerTests.cs", "test/DemaConsulting.Rendering.Layout.Tests/Engine/Layered/CrossingMinimizerRecursionTests.cs", "test/DemaConsulting.Rendering.Layout.Tests/Engine/Layered/CrossingMinimizerTests.cs", "test/DemaConsulting.Rendering.Layout.Tests/Engine/Layered/CycleBreakerTests.cs", "test/DemaConsulting.Rendering.Layout.Tests/Engine/Layered/HierarchyMergeRegionBuilderTests.cs", "test/DemaConsulting.Rendering.Layout.Tests/Engine/Layered/LayerAssignerTests.cs", "test/DemaConsulting.Rendering.Layout.Tests/Engine/Layered/LayeredGraphTests.cs", "test/DemaConsulting.Rendering.Layout.Tests/Engine/Layered/LayeredLayoutPipelineTests.cs", "test/DemaConsulting.Rendering.Layout.Tests/Engine/Layered/LayeredPipelineEquivalenceTests.cs", "test/DemaConsulting.Rendering.Layout.Tests/Engine/Layered/LegacyInterconnectionLayoutEngineOracle.cs", "test/DemaConsulting.Rendering.Layout.Tests/Engine/Layered/LongEdgeJoinerTests.cs", "test/DemaConsulting.Rendering.Layout.Tests/Engine/Layered/LongEdgeSplitterTests.cs", "test/DemaConsulting.Rendering.Layout.Tests/Engine/Layered/MergeRegionDecomposerTests.cs", "test/DemaConsulting.Rendering.Layout.Tests/Engine/Layered/MergeRegionGraphAssemblerTests.cs", "test/DemaConsulting.Rendering.Layout.Tests/Engine/Layered/OrthogonalRouterBackEdgeTests.cs", "test/DemaConsulting.Rendering.Layout.Tests/Engine/Layered/OrthogonalRouterTests.cs", "test/DemaConsulting.Rendering.Layout.Tests/Engine/Layered/PortDistributorTests.cs");
            designFiles = ("docs/design/rendering-layout/engine/layered-pipeline.md");
            verificationFiles = ("docs/verification/rendering-layout/engine/layered-pipeline.md");
            requirementFiles = ("docs/reqstream/rendering-layout/engine/layered-pipeline.yaml");
        }
    }
}
